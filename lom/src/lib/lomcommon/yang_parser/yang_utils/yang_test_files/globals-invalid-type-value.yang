module globals-invalid-type-value {

    yang-version 1.1;

    namespace "http://github.com/sonic-net/actions-sample-config-for-uts";

    prefix dtm;

    organization
        "SONiC";

    contact
        "Device";

    description
        "Global configurations for Device health agent for UTs";

    revision 2023-06-28 {
        description
            "Initial revision.";
    }
	
    leaf MAX_SEQ_TIMEOUT_SECS {
        type int32;
	description "invalid int32 type value";
	default 55;
	config true;
    }
}
